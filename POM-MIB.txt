POM-MIB DEFINITIONS ::= BEGIN

IMPORTS
	MODULE-IDENTITY, OBJECT-TYPE, Unsigned32, enterprises,
	Counter32, Counter64, Gauge32, TimeTicks FROM SNMPv2-SMI
	TEXTUAL-CONVENTION, DisplayString, TruthValue FROM SNMPv2-TC
;

packet-o-matic MODULE-IDENTITY
	LAST-UPDATED	"200910300000Z"
	ORGANIZATION	"www.packet-o-matic.org"
	CONTACT-INFO	"email: gmsoft@tuxicoman.be"
	DESCRIPTION	"Packet-o-matic MIB"

	REVISION	"200910300000Z"
	DESCRIPTION	"Initial revision"

	::= { enterprises 31355 2 1 }

--
-- Misc definition
--

GenericTableIndex ::= TEXTUAL-CONVENTION
	DISPLAY-HINT	"d"
	STATUS		current
	DESCRIPTION	"Generic index syntax"
	SYNTAX		Unsigned32 (1..4294967295)

--
-- Core definition
--

core	OBJECT IDENTIFIER ::= { packet-o-matic 1 }

coreRunning OBJECT-TYPE
	SYNTAX		TruthValue
	MAX-ACCESS	read-write
	STATUS		current
	DESCRIPTION	"Set to false to stop packet-o-matic"
	::= { core 1 }

coreDebugLevel OBJECT-TYPE
	SYNTAX		Unsigned32
	MAX-ACCESS	read-write
	STATUS		current
	DESCRIPTION	"Debug level of the console"
	::= { core 2 }

coreParamTable OBJECT-TYPE
	SYNTAX		SEQUENCE OF CoreParamEntry
	MAX-ACCESS	not-accessible
	STATUS		current
	DESCRIPTION	"The core parameters"
	::= { core 3 }

coreParamEntry OBJECT-TYPE
	SYNTAX		CoreParamEntry
	MAX-ACCESS	not-accessible
	STATUS		current
	DESCRIPTION	"A core parameter"
	INDEX		{ coreParamIndex }
	::= { coreParamTable 1 }

CoreParamEntry ::=
	SEQUENCE {
		coreParamIndex	GenericTableIndex,
		coreParamName	DisplayString,
		coreParamValue	DisplayString,
		coreParamUnit	DisplayString,
		coreParamType	DisplayString,
		coreParamDescr	DisplayString
	}

coreParamIndex OBJECT-TYPE
	SYNTAX		GenericTableIndex
	MAX-ACCESS	read-only
	STATUS		current
	DESCRIPTION	"Index of a core parameter"
	::= { coreParamEntry 1 }


coreParamName OBJECT-TYPE
	SYNTAX		DisplayString
	MAX-ACCESS	read-only
	STATUS		current
	DESCRIPTION	"Name a core parameter"
	::= { coreParamEntry 2 }

coreParamValue OBJECT-TYPE
	SYNTAX		DisplayString
	MAX-ACCESS	read-write
	STATUS		current
	DESCRIPTION	"Value of a core parameter"
	::= { coreParamEntry 3 }

coreParamUnit OBJECT-TYPE
	SYNTAX		DisplayString
	MAX-ACCESS	read-only
	STATUS		current
	DESCRIPTION	"Unit of a core parameter"
	::= { coreParamEntry 4 }

coreParamType OBJECT-TYPE
	SYNTAX		DisplayString
	MAX-ACCESS	read-only
	STATUS		current
	DESCRIPTION	"Type of a core parameter"
	::= { coreParamEntry 5 }

coreParamDescr OBJECT-TYPE
	SYNTAX		DisplayString
	MAX-ACCESS	read-only
	STATUS		current
	DESCRIPTION	"Description of a core parameter"
	::= { coreParamEntry 6 }


corePerf OBJECT IDENTIFIER ::={ core 4 }

coreVersion OBJECT-TYPE
	SYNTAX		DisplayString
	MAX-ACCESS	read-only
	STATUS		current
	DESCRIPTION	"Version of packet-o-matic"
	::= { corePerf 1 }

coreUpTime OBJECT-TYPE
	SYNTAX		TimeTicks
	MAX-ACCESS	read-only
	STATUS		current
	DESCRIPTION	"UpTime of packet-o-matic"
	::= { corePerf 2 }

coreRingBufferPackets OBJECT-TYPE
	SYNTAX		Gauge32
	MAX-ACCESS	read-only
	STATUS		current
	DESCRIPTION	"Number of packets currently in the ring buffer"
	::= { corePerf 3 }

coreRingBufferTotPackets OBJECT-TYPE
	SYNTAX		Counter64
	MAX-ACCESS	read-only
	STATUS		current
	DESCRIPTION	"Total number of packets which went into the ring buffer"
	::= { corePerf 4 }

coreRingBufferDroppedPackets OBJECT-TYPE
	SYNTAX		Counter64
	MAX-ACCESS	read-only
	STATUS		current
	DESCRIPTION	"Total number of packets dropped in the ring buffer"
	::= { corePerf 5 }

coreRingBufferOverflow OBJECT-TYPE
	SYNTAX		Counter64
	MAX-ACCESS	read-only
	STATUS		current
	DESCRIPTION	"Number of time the ring buffer overflowed"
	::= { corePerf 6 }

--
-- Input definition
--

input	OBJECT IDENTIFIER ::= { packet-o-matic 2 }

inputConfig OBJECT IDENTIFIER  ::= { input 1 }

inputType OBJECT-TYPE
	SYNTAX		DisplayString
	MAX-ACCESS	read-write
	STATUS		current
	DESCRIPTION	"The input type"
	::= { inputConfig 1 }

inputMode OBJECT-TYPE
	SYNTAX		DisplayString
	MAX-ACCESS	read-write
	STATUS		current
	DESCRIPTION	"The input mode"
	::= { inputConfig 2 }


inputParamTable OBJECT-TYPE
	SYNTAX		SEQUENCE OF InputParamEntry
	MAX-ACCESS	not-accessible
	STATUS		current
	DESCRIPTION	"The input parameters"
	::= { inputConfig 3 }

inputParamEntry OBJECT-TYPE
	SYNTAX		InputParamEntry
	MAX-ACCESS	not-accessible
	STATUS		current
	DESCRIPTION	"An input parameter"
	INDEX		{ inputParamIndex }
	::= { inputParamTable 1 }

InputParamEntry ::=
	SEQUENCE {
		inputParamIndex	GenericTableIndex,
		inputParamName	DisplayString,
		inputParamValue	DisplayString,
		inputParamUnit	DisplayString,
		inputParamType	DisplayString,
		inputParamDescr	DisplayString
	}

inputParamIndex OBJECT-TYPE
	SYNTAX		GenericTableIndex
	MAX-ACCESS	read-only
	STATUS		current
	DESCRIPTION	"Index of an input parameter"
	::= { inputParamEntry 1 }

inputParamName OBJECT-TYPE
	SYNTAX		DisplayString
	MAX-ACCESS	read-only
	STATUS		current
	DESCRIPTION	"Name an input parameter"
	::= { inputParamEntry 2 }

inputParamValue	OBJECT-TYPE
	SYNTAX		DisplayString
	MAX-ACCESS	read-write
	STATUS		current
	DESCRIPTION	"Value of an input parameter"
	::= { inputParamEntry 3 }

inputParamUnit	OBJECT-TYPE
	SYNTAX		DisplayString
	MAX-ACCESS	read-only
	STATUS		current
	DESCRIPTION	"Unit of an input parameter"
	::= { inputParamEntry 4 }

inputParamType	OBJECT-TYPE
	SYNTAX		DisplayString
	MAX-ACCESS	read-only
	STATUS		current
	DESCRIPTION	"Type of an input parameter"
	::= { inputParamEntry 5 }

inputParamDescr	OBJECT-TYPE
	SYNTAX		DisplayString
	MAX-ACCESS	read-only
	STATUS		current
	DESCRIPTION	"Description of an input parameter"
	::= { inputParamEntry 6 }

inputRunning OBJECT-TYPE
	SYNTAX		TruthValue
	MAX-ACCESS	read-write
	STATUS		current
	DESCRIPTION	"True if the input is started"
	::= { inputConfig 4 }

inputModesTable OBJECT-TYPE
	SYNTAX		SEQUENCE OF InputModesEntry
	MAX-ACCESS	not-accessible
	STATUS		current
	DESCRIPTION	"Possible input modes"
	::= { inputConfig 5 }

inputModesEntry OBJECT-TYPE
	SYNTAX		InputModesEntry
	MAX-ACCESS	not-accessible
	STATUS		current
	DESCRIPTION	"An input mode description"
	INDEX		{ inputParamIndex }
	::= { inputModesTable 1 }

InputModesEntry ::=
	SEQUENCE {
		inputModesIndex	GenericTableIndex,
		inputModesName	DisplayString,
		inputModesDescr	DisplayString
	}

inputModesIndex OBJECT-TYPE
	SYNTAX		GenericTableIndex
	MAX-ACCESS	read-only
	STATUS		current
	DESCRIPTION	"Index of the input modes table"
	::= { inputModesEntry 1 }

inputModesName OBJECT-TYPE
	SYNTAX		DisplayString
	MAX-ACCESS	read-only
	STATUS		current
	DESCRIPTION	"Name an input mode"
	::= { inputModesEntry 2 }

inputModesDescr OBJECT-TYPE
	SYNTAX		DisplayString
	MAX-ACCESS	read-write
	STATUS		current
	DESCRIPTION	"Description of an input mode"
	::= { inputModesEntry 3 }

inputSerial OBJECT-TYPE
	SYNTAX		Counter32
	MAX-ACCESS	read-only
	STATUS		current
	DESCRIPTION	"Number of changes of the input"
	::= { inputConfig 6 }


-- Input perf stuff

inputPerf OBJECT IDENTIFIER ::= { input 2 }

inputBytesIn OBJECT-TYPE
	SYNTAX		Counter64
	MAX-ACCESS	read-only
	STATUS		current
	DESCRIPTION	"Number of bytes read by the input"
	::= { inputPerf 1 }

inputPacketsIn OBJECT-TYPE
	SYNTAX		Counter64
	MAX-ACCESS	read-only
	STATUS		current
	DESCRIPTION	"Numer of packets read by the input"
	::= { inputPerf 2 }

inputUpTime OBJECT-TYPE
	SYNTAX		TimeTicks
	MAX-ACCESS	read-only
	STATUS		current
	DESCRIPTION	"UpTime of the input"
	::= { inputPerf 3 }

inputSnapLen OBJECT-TYPE
	SYNTAX		Gauge32
	MAX-ACCESS	read-only
	STATUS		current
	DESCRIPTION
		"Snap length of the inupt. Represent the maximum
		packet size which will be captured by this input.
		This counter is only available when the input is
		running."
	::= { inputPerf 4 }

inputIsLive OBJECT-TYPE
	SYNTAX		TruthValue
	MAX-ACCESS	read-only
	STATUS		current
	DESCRIPTION
		"True if packets are captured from real network
		interface currently reading packets or false if
		packets are read from a saved file."
	::= { inputPerf 5 }

-- Extra counters

inputPerfExtraCounterTable OBJECT-TYPE
	SYNTAX		SEQUENCE OF InputPerfExtraCounterEntry
	MAX-ACCESS	not-accessible
	STATUS		current
	DESCRIPTION	"The list of extra input performance objects"
	::= { inputPerf 6 }

inputPerfExtraCounterEntry OBJECT-TYPE
	SYNTAX		InputPerfExtraCounterEntry
	MAX-ACCESS	not-accessible
	STATUS		current
	DESCRIPTION	"One input performance object"
	INDEX		{ inputPerfExtraCounterIndex }
	::= { inputPerfExtraCounterTable 1 }

InputPerfExtraCounterEntry ::=
	SEQUENCE {
		inputPerfExtraCounterIndex	GenericTableIndex,
		inputPerfExtraCounterName	DisplayString,
		inputPerfExtraCounterValue	Counter64,
		inputPerfExtraCounterDescr	DisplayString
	}

inputPerfExtraCounterIndex OBJECT-TYPE
	SYNTAX		GenericTableIndex
	MAX-ACCESS	read-only
	STATUS		current
	DESCRIPTION	"Index of extra performance objects for input"
	::= { inputPerfExtraCounterEntry 1 }

inputPerfExtraCounterName OBJECT-TYPE
	SYNTAX		DisplayString
	MAX-ACCESS	read-only
	STATUS		current
	DESCRIPTION	"Name of extra performance objects for input"
	::= { inputPerfExtraCounterEntry 2 }

inputPerfExtraCounterValue OBJECT-TYPE
	SYNTAX		Counter64
	MAX-ACCESS	read-only
	STATUS		current
	DESCRIPTION	"Value of extra performance objects for input"
	::= { inputPerfExtraCounterEntry 3 }

inputPerfExtraCounterDescr OBJECT-TYPE
	SYNTAX		DisplayString
	MAX-ACCESS	read-only
	STATUS		current
	DESCRIPTION	"Description of extra performance objects for input"
	::= { inputPerfExtraCounterEntry 4 }

-- Input perf extra gauges

inputPerfExtraGaugeTable OBJECT-TYPE
	SYNTAX		SEQUENCE OF InputPerfExtraGaugeEntry
	MAX-ACCESS	not-accessible
	STATUS		current
	DESCRIPTION	"The list of extra input performance objects"
	::= { inputPerf 7 }

inputPerfExtraGaugeEntry OBJECT-TYPE
	SYNTAX		InputPerfExtraGaugeEntry
	MAX-ACCESS	not-accessible
	STATUS		current
	DESCRIPTION	"One input performance object"
	INDEX		{ inputPerfExtraGaugeIndex }
	::= { inputPerfExtraGaugeTable 1 }

InputPerfExtraGaugeEntry ::=
	SEQUENCE {
		inputPerfExtraGaugeIndex	GenericTableIndex,
		inputPerfExtraGaugeName		DisplayString,
		inputPerfExtraGaugeValue	Gauge32,
		inputPerfExtraGaugeDescr	DisplayString
	}

inputPerfExtraGaugeIndex OBJECT-TYPE
	SYNTAX		GenericTableIndex
	MAX-ACCESS	read-only
	STATUS		current
	DESCRIPTION	"Index of extra performance objects for input"
	::= { inputPerfExtraGaugeEntry 1 }

inputPerfExtraGaugeName OBJECT-TYPE
	SYNTAX		DisplayString
	MAX-ACCESS	read-only
	STATUS		current
	DESCRIPTION	"Name of extra performance objects for input"
	::= { inputPerfExtraGaugeEntry 2 }

inputPerfExtraGaugeValue OBJECT-TYPE
	SYNTAX		Gauge32
	MAX-ACCESS	read-only
	STATUS		current
	DESCRIPTION	"Value of extra performance objects for input"
	::= { inputPerfExtraGaugeEntry 3 }

inputPerfExtraGaugeDescr OBJECT-TYPE
	SYNTAX		DisplayString
	MAX-ACCESS	read-only
	STATUS		current
	DESCRIPTION	"Description of extra performance objects for input"
	::= { inputPerfExtraGaugeEntry 4 }

--
-- Rules definition
--

rule OBJECT IDENTIFIER ::= { packet-o-matic 3 }

ruleTable OBJECT-TYPE
	SYNTAX		SEQUENCE OF RuleEntry
	MAX-ACCESS	not-accessible
	STATUS		current
	DESCRIPTION	"The list of rules"
	::= { rule 1 }

ruleEntry OBJECT-TYPE
	SYNTAX		RuleEntry
	MAX-ACCESS	not-accessible
	STATUS		current
	DESCRIPTION	"A rule"
	INDEX		{ ruleIndex }
	::= { ruleTable 1 }

RuleEntry ::=
	SEQUENCE {
		ruleIndex		GenericTableIndex,
		ruleCliIndex		Unsigned32,
		ruleDefinition		DisplayString,
		ruleDescription		DisplayString,
		ruleEnabled		TruthValue,
		ruleSerial		Counter32,
		ruleTargetSerial	Counter32
	}

ruleIndex OBJECT-TYPE
	SYNTAX		GenericTableIndex
	MAX-ACCESS	read-only
	STATUS		current
	DESCRIPTION	"Index of the rule"
	::= { ruleEntry 1 }

ruleCliIndex OBJECT-TYPE
	SYNTAX		Unsigned32
	MAX-ACCESS	read-only
	STATUS		current
	DESCRIPTION	"Index of the rule in the CLI"
	::= { ruleEntry 2 }

ruleDefinition OBJECT-TYPE
	SYNTAX		DisplayString
	MAX-ACCESS	read-write
	STATUS		current
	DESCRIPTION	"Definition of the rule"
	::= { ruleEntry 3 }

ruleDescription OBJECT-TYPE
	SYNTAX		DisplayString
	MAX-ACCESS	read-write
	STATUS		current
	DESCRIPTION	"Description of the rule"
	::= { ruleEntry 4 }

ruleEnabled OBJECT-TYPE
	SYNTAX		TruthValue
	MAX-ACCESS	read-write
	STATUS		current
	DESCRIPTION	"Define if the rule is enabled or not"
	::= { ruleEntry 5 }

ruleSerial OBJECT-TYPE
	SYNTAX		Counter32
	MAX-ACCESS	read-only
	STATUS		current
	DESCRIPTION 	"Number of changes for this rule"
	::= { ruleEntry 6 }

ruleTargetSerial OBJECT-TYPE
	SYNTAX		Counter32
	MAX-ACCESS	read-only
	STATUS		current
	DESCRIPTION 	"Number of changes for the targets of this rule"
	::= { ruleEntry 7 }

rulesSerial OBJECT-TYPE
	SYNTAX		Counter32
	MAX-ACCESS	read-only
	STATUS		current
	DESCRIPTION	"Number of changes for the rules"
	::= { rule 2 }

--- Rules perf stuff

rulePerfTable OBJECT-TYPE
	SYNTAX		SEQUENCE OF RulePerfEntry
	MAX-ACCESS	not-accessible
	STATUS		current
	DESCRIPTION	"The list of rules performance counters"
	::= { rule 3 }

rulePerfEntry OBJECT-TYPE
	SYNTAX		RulePerfEntry
	MAX-ACCESS	not-accessible
	STATUS		current
	DESCRIPTION	"Performance objects for a rule"
	INDEX		{ rulePerfIndex }
	::= { rulePerfTable 1 }

RulePerfEntry ::=
	SEQUENCE {
		rulePerfIndex		GenericTableIndex,
		ruleBytes		Counter64,
		rulePackets		Counter64,
		ruleUpTime		TimeTicks
	}

rulePerfIndex OBJECT-TYPE
	SYNTAX		GenericTableIndex
	MAX-ACCESS	read-only
	STATUS		current
	DESCRIPTION	"Index of the rule performance objects"
	::= { rulePerfEntry 1 }

ruleBytes OBJECT-TYPE
	SYNTAX		Counter64
	MAX-ACCESS	read-only
	STATUS		current
	DESCRIPTION	"Number of bytes matched by the rule"
	::= { rulePerfEntry 2 }

rulePackets OBJECT-TYPE
	SYNTAX		Counter64
	MAX-ACCESS	read-only
	STATUS		current
	DESCRIPTION	"Number of packets matched by the rule"
	::= { rulePerfEntry 3 }

ruleUpTime OBJECT-TYPE
	SYNTAX		TimeTicks
	MAX-ACCESS	read-only
	STATUS		current
	DESCRIPTION	"Time for which the rule has been enabled"
	::= { rulePerfEntry 4 }

---
--- Target definition
---

target OBJECT IDENTIFIER ::= { packet-o-matic 4 }

targetConfig OBJECT IDENTIFIER ::= { target 1 }

targetTable OBJECT-TYPE
	SYNTAX		SEQUENCE OF TargetEntry
	MAX-ACCESS	not-accessible
	STATUS		current
	DESCRIPTION	"The list of targets"
	::= { targetConfig 1 }

targetEntry OBJECT-TYPE
	SYNTAX		TargetEntry
	MAX-ACCESS	not-accessible
	STATUS		current
	DESCRIPTION	"A target"
	INDEX		{ targetRuleIndex, targetIndex }
	::= { targetTable 1 }

TargetEntry ::=
	SEQUENCE {
		targetRuleIndex		GenericTableIndex,
		targetIndex		GenericTableIndex,
		targetCliIndex		Unsigned32,
		targetType		DisplayString,
		targetDescription	DisplayString,
		targetStarted		TruthValue,
		targetSerial		Counter32
	}

targetRuleIndex OBJECT-TYPE
	SYNTAX		GenericTableIndex
	MAX-ACCESS	read-only
	STATUS		current
	DESCRIPTION	"Rule index of the target"
	::= { targetEntry 1 }

targetIndex OBJECT-TYPE
	SYNTAX		GenericTableIndex
	MAX-ACCESS	read-only
	STATUS		current
	DESCRIPTION	"Index of the target"
	::= { targetEntry 2 }

targetCliIndex OBJECT-TYPE
	SYNTAX		Unsigned32
	MAX-ACCESS	read-only
	STATUS		current
	DESCRIPTION	"Index of the target in the CLI"
	::= { targetEntry 3 }

targetType OBJECT-TYPE
	SYNTAX		DisplayString
	MAX-ACCESS	read-only
	STATUS		current
	DESCRIPTION	"Type of the target"
	::= { targetEntry 4 }

targetDescription OBJECT-TYPE
	SYNTAX		DisplayString
	MAX-ACCESS	read-write
	STATUS		current
	DESCRIPTION	"Description"
	::= { targetEntry 5 }

targetStarted OBJECT-TYPE
	SYNTAX		TruthValue
	MAX-ACCESS	read-write
	STATUS		current
	DESCRIPTION	"Running status of the target"
	::= { targetEntry 6 }

targetSerial OBJECT-TYPE
	SYNTAX		Counter32
	MAX-ACCESS	read-only
	STATUS		current
	DESCRIPTION	"Number of changes for this target"
	::= { targetEntry 7 }



targetParamTable OBJECT-TYPE
	SYNTAX		SEQUENCE OF TargetParamEntry
	MAX-ACCESS	not-accessible
	STATUS		current
	DESCRIPTION	"The list of target parameters"
	::= { targetConfig 2 }

targetParamEntry OBJECT-TYPE
	SYNTAX		TargetParamEntry
	MAX-ACCESS	not-accessible
	STATUS		current
	DESCRIPTION	"A target parameter"
	INDEX		{ targetParamRuleIndex, targetParamTargetIndex, targetParamIndex }
	::= { targetParamTable 1 }

TargetParamEntry ::=
	SEQUENCE {
		targetParamRuleIndex	GenericTableIndex,
		targetParamTargetIndex	GenericTableIndex,
		targetParamIndex	GenericTableIndex,
		targetParamName		DisplayString,
		targetParamValue	DisplayString,
		targetParamUnit		DisplayString,
		targetParamType		DisplayString,
		targetParamDescr	DisplayString
	}

targetParamRuleIndex OBJECT-TYPE
	SYNTAX		GenericTableIndex
	MAX-ACCESS	read-only
	STATUS		current
	DESCRIPTION	"Rule index of the target parameter"
	::= { targetParamEntry 1 }

targetParamTargetIndex OBJECT-TYPE
	SYNTAX		GenericTableIndex
	MAX-ACCESS	read-only
	STATUS		current
	DESCRIPTION	"Index of the target"
	::= { targetParamEntry 2 }

targetParamIndex OBJECT-TYPE
	SYNTAX		GenericTableIndex
	MAX-ACCESS	read-only
	STATUS		current
	DESCRIPTION	"Index of the target parameter"
	::= { targetParamEntry 3 }

targetParamName OBJECT-TYPE
	SYNTAX		DisplayString
	MAX-ACCESS	read-only
	STATUS		current
	DESCRIPTION	"Name of the target parameter"
	::= { targetParamEntry 4 }

targetParamValue OBJECT-TYPE
	SYNTAX		DisplayString
	MAX-ACCESS	read-write
	STATUS		current
	DESCRIPTION	"Value of the target parameter"
	::= { targetParamEntry 5 }

targetParamUnit OBJECT-TYPE
	SYNTAX		DisplayString
	MAX-ACCESS	read-only
	STATUS		current
	DESCRIPTION	"Unit of the target parameter"
	::= { targetParamEntry 6 }

targetParamType OBJECT-TYPE
	SYNTAX		DisplayString
	MAX-ACCESS	read-only
	STATUS		current
	DESCRIPTION	"Type of the target parameter"
	::= { targetParamEntry 7 }

targetParamDescr OBJECT-TYPE
	SYNTAX		DisplayString
	MAX-ACCESS	read-only
	STATUS		current
	DESCRIPTION	"Name of the target parameter"
	::= { targetParamEntry 8 }

targetsSerial OBJECT-TYPE
	SYNTAX		Counter32
	MAX-ACCESS	read-only
	STATUS		current
	DESCRIPTION	"Number of changes for the targets"
	::= { targetConfig 3 }


targetPerf OBJECT IDENTIFIER  ::= { target 2 }

targetPerfTable OBJECT-TYPE
	SYNTAX		SEQUENCE OF TargetPerfEntry
	MAX-ACCESS	not-accessible
	STATUS		current
	DESCRIPTION	"The list of target performance objects"
	::= { targetPerf 1 }

targetPerfEntry OBJECT-TYPE
	SYNTAX		TargetPerfEntry
	MAX-ACCESS	not-accessible
	STATUS		current
	DESCRIPTION	"A target performance object"
	INDEX		{ targetPerfRuleIndex, targetPerfTargetIndex }
	::= { targetPerfTable 1 }

TargetPerfEntry ::=
	SEQUENCE {
		targetPerfRuleIndex	GenericTableIndex,
		targetPerfTargetIndex	GenericTableIndex,
		targetBytes		Counter64,
		targetPackets		Counter64,
		targetUpTime		TimeTicks
	}

targetPerfRuleIndex OBJECT-TYPE
	SYNTAX		GenericTableIndex
	MAX-ACCESS	read-only
	STATUS		current
	DESCRIPTION	"Rule index of the target performance objects"
	::= { targetPerfEntry 1 }

targetPerfTargetIndex OBJECT-TYPE
	SYNTAX		GenericTableIndex
	MAX-ACCESS	read-only
	STATUS		current
	DESCRIPTION	"Index of the target"
	::= { targetPerfEntry 2 }

targetBytes OBJECT-TYPE
	SYNTAX		Counter64
	MAX-ACCESS	read-only
	STATUS		current
	DESCRIPTION	"Number of bytes sent to the target for processing"
	::= { targetPerfEntry 3 }

targetPackets OBJECT-TYPE
	SYNTAX		Counter64
	MAX-ACCESS	read-only
	STATUS		current
	DESCRIPTION	"Number of packets sent to the target for processing"
	::= { targetPerfEntry 4 }

targetUpTime OBJECT-TYPE
	SYNTAX		TimeTicks
	MAX-ACCESS	read-only
	STATUS		current
	DESCRIPTION	"Time for which the target has been started"
	::= { targetPerfEntry 5 }



targetPerfExtraCounterTable OBJECT-TYPE
	SYNTAX		SEQUENCE OF TargetPerfExtraCounterEntry
	MAX-ACCESS	not-accessible
	STATUS		current
	DESCRIPTION	"The list of target extra counters performance objects"
	::= { targetPerf 2 }

targetPerfExtraCounterEntry OBJECT-TYPE
	SYNTAX		TargetPerfExtraCounterEntry
	MAX-ACCESS	not-accessible
	STATUS		current
	DESCRIPTION	"A target performance extra counter object"
	INDEX		{ targetPerfExtraCounterRuleIndex, targetPerfExtraCounterTargetIndex, targetPerfExtraCounterIndex }
	::= { targetPerfExtraCounterTable 1 }

TargetPerfExtraCounterEntry ::=
	SEQUENCE {
		targetPerfExtraCounterRuleIndex		GenericTableIndex,
		targetPerfExtraCounterTargetIndex	GenericTableIndex,
		targetPerfExtraCounterIndex		GenericTableIndex,
		targetPerfExtraCounterName		DisplayString,
		targetPerfExtraCounterValue		Counter64,
		targetPerfExtraCounterDescr		DisplayString
	}

targetPerfExtraCounterRuleIndex OBJECT-TYPE
	SYNTAX		GenericTableIndex
	MAX-ACCESS	read-only
	STATUS		current
	DESCRIPTION	"Rule index of the target extra counter performance objects"
	::= { targetPerfExtraCounterEntry 1 }

targetPerfExtraCounterTargetIndex OBJECT-TYPE
	SYNTAX		GenericTableIndex
	MAX-ACCESS	read-only
	STATUS		current
	DESCRIPTION	"Index of the target"
	::= { targetPerfExtraCounterEntry 2 }

targetPerfExtraCounterIndex OBJECT-TYPE
	SYNTAX		GenericTableIndex
	MAX-ACCESS	read-only
	STATUS		current
	DESCRIPTION	"Index of the extra counter performance object"
	::= { targetPerfExtraCounterEntry 3 }

targetPerfExtraCounterName OBJECT-TYPE
	SYNTAX		DisplayString
	MAX-ACCESS	read-only
	STATUS		current
	DESCRIPTION	"Name of the extra counter performance object"
	::= { targetPerfExtraCounterEntry 4 }

targetPerfExtraCounterValue OBJECT-TYPE
	SYNTAX		Counter64
	MAX-ACCESS	read-only
	STATUS		current
	DESCRIPTION	"Value of the extra counter performance object"
	::= { targetPerfExtraCounterEntry 5 }

targetPerfExtraCounterDescr OBJECT-TYPE
	SYNTAX		DisplayString
	MAX-ACCESS	read-only
	STATUS		current
	DESCRIPTION	"Description  of the extra counter performance object"
	::= { targetPerfExtraCounterEntry 6 }



targetPerfExtraGaugeTable OBJECT-TYPE
	SYNTAX		SEQUENCE OF TargetPerfExtraGaugeEntry
	MAX-ACCESS	not-accessible
	STATUS		current
	DESCRIPTION	"The list of target extra counters performance objects"
	::= { targetPerf 3 }

targetPerfExtraGaugeEntry OBJECT-TYPE
	SYNTAX		TargetPerfExtraGaugeEntry
	MAX-ACCESS	not-accessible
	STATUS		current
	DESCRIPTION	"A target performance extra counter object"
	INDEX		{ targetPerfExtraGaugeRuleIndex, targetPerfExtraGaugeTargetIndex, targetPerfExtraGaugeIndex }
	::= { targetPerfExtraGaugeTable 1 }

TargetPerfExtraGaugeEntry ::=
	SEQUENCE {
		targetPerfExtraGaugeRuleIndex		GenericTableIndex,
		targetPerfExtraGaugeTargetIndex	GenericTableIndex,
		targetPerfExtraGaugeIndex		GenericTableIndex,
		targetPerfExtraGaugeName		DisplayString,
		targetPerfExtraGaugeValue		Gauge64,
		targetPerfExtraGaugeDescr		DisplayString
	}

targetPerfExtraGaugeRuleIndex OBJECT-TYPE
	SYNTAX		GenericTableIndex
	MAX-ACCESS	read-only
	STATUS		current
	DESCRIPTION	"Rule index of the target extra counter performance objects"
	::= { targetPerfExtraGaugeEntry 1 }

targetPerfExtraGaugeTargetIndex OBJECT-TYPE
	SYNTAX		GenericTableIndex
	MAX-ACCESS	read-only
	STATUS		current
	DESCRIPTION	"Index of the target"
	::= { targetPerfExtraGaugeEntry 2 }

targetPerfExtraGaugeIndex OBJECT-TYPE
	SYNTAX		GenericTableIndex
	MAX-ACCESS	read-only
	STATUS		current
	DESCRIPTION	"Index of the extra counter performance object"
	::= { targetPerfExtraGaugeEntry 3 }

targetPerfExtraGaugeName OBJECT-TYPE
	SYNTAX		DisplayString
	MAX-ACCESS	read-only
	STATUS		current
	DESCRIPTION	"Name of the extra counter performance object"
	::= { targetPerfExtraGaugeEntry 4 }

targetPerfExtraGaugeValue OBJECT-TYPE
	SYNTAX		Gauge64
	MAX-ACCESS	read-only
	STATUS		current
	DESCRIPTION	"Value of the extra counter performance object"
	::= { targetPerfExtraGaugeEntry 5 }

targetPerfExtraGaugeDescr OBJECT-TYPE
	SYNTAX		DisplayString
	MAX-ACCESS	read-only
	STATUS		current
	DESCRIPTION	"Description  of the extra counter performance object"
	::= { targetPerfExtraGaugeEntry 6 }
---
--- Match definition
---

match OBJECT IDENTIFIER ::= { packet-o-matic 5 }


---
--- Helper definition
---

helper OBJECT IDENTIFIER ::= { packet-o-matic 6 }


---
--- Conntrack definition
---

conntrack OBJECT IDENTIFIER ::= { packet-o-matic 7 }

conntrackConfig OBJECT IDENTIFIER ::= { conntrack 1 }


conntrackPerf OBJECT IDENTIFIER ::= { conntrack 2 }

END
